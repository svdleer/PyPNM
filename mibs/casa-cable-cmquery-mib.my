--
-- casa-cable-cmquery-mib.my
-- 

	CASA-CABLE-CMQUERY-MIB DEFINITIONS ::= BEGIN
 
		IMPORTS
			casa, casaMgmt
				FROM CASA-MIB			
			ifIndex			
				FROM IF-MIB			
			OBJECT-GROUP, MODULE-COMPLIANCE			
				FROM SNMPv2-CONF			
			IpAddress, Integer32, Unsigned32, OBJECT-TYPE, MODULE-IDENTITY			
				FROM SNMPv2-SMI			
			MacAddress, TEXTUAL-CONVENTION, DisplayString
				FROM SNMPv2-TC
			IfDirection
				FROM DOCS-IF3-MIB
			TenthdB,
			TenthdBmV
				FROM DOCS-IF-MIB;
				
		
		-- 1.3.6.1.4.1.20858.10.18
		casaCmQueryMib MODULE-IDENTITY 
			LAST-UPDATED "201202270000Z"		-- February 27, 2012 at 00:00 GMT
			ORGANIZATION 
				"Casa Systems Inc"
			CONTACT-INFO 
				"CASA SYSTEMS INC.
				100 Old River Road 
				Andover, MA 01810
				USA
				
				Tel: +1 978-688-6706
				e-mail: support@casa-systems.com"
			DESCRIPTION 
				"This is the enterprise MIB Module for CASA systems CMTS."
			REVISION "201202271117Z"		-- February 27, 2012 at 11:17 GMT
			DESCRIPTION 
				"Change to reference TenthdBmV and TenthdB from DOCS-IF-MIB"
			::= { casaMgmt 18 }

			
	CasaDocsisUpstreamType ::= TEXTUAL-CONVENTION
			STATUS          current
			DESCRIPTION     "Indicates the casaDOCSIS Upstream Channel Type."
			SYNTAX          INTEGER {
					unknown (0),
					tdma (1),
					atdma (2),
					scdma (3),
					tdmaAndAtdma (4),
					ofdma (5)
				}		
				

		-- 1.3.6.1.4.1.20858.10.18.1
		casaCmQueryMibObjects OBJECT IDENTIFIER ::= { casaCmQueryMib 1 }
		
		-- 1.3.6.1.4.1.20858.10.18.1.1
		casaCmQueryTable OBJECT-TYPE
			SYNTAX SEQUENCE OF CasaCmQueryEntry
			MAX-ACCESS not-accessible
			STATUS current
			DESCRIPTION
				"describes the PHY signal quality and Tx/Rx parameter of cable modem.  
				"
			::= { casaCmQueryMibObjects 1 }

		
		-- 1.3.6.1.4.1.20858.10.18.1.1.1
		casaCmQueryEntry OBJECT-TYPE
			SYNTAX CasaCmQueryEntry
			MAX-ACCESS not-accessible
			STATUS current
			DESCRIPTION
				"describes the PHY signal quality and Tx/Rx parameter of cable modem,index of this table is casaQueryCmMacAddress. 
				"
			INDEX { casaQueryCmMacAddress }
			::= { casaCmQueryTable 1 }

		
		CasaCmQueryEntry ::=
			SEQUENCE { 
				casaQueryCmMacAddress
					MacAddress,
				casaQueryCmIpAddress
					IpAddress,
				casaQueryCmTxTimeOffset
					Unsigned32,
				casaQueryCmMicroReflection
					Integer32,
				casaQueryCmStatusTxPower
					TenthdBmV,
				casaQueryCmStatusRxPower
					TenthdBmV,
				casaQueryCmSigQSignalNoise
					TenthdB,
				casaQueryCmtsSigQSignalNoise
					TenthdB,
				cmSysDesc
					DisplayString,
				configFile
					DisplayString
			 }

		-- 1.3.6.1.4.1.20858.10.18.1.1.1.1
		casaQueryCmMacAddress OBJECT-TYPE
			SYNTAX MacAddress
			MAX-ACCESS not-accessible
			STATUS current
			DESCRIPTION
				"The cable modem Mac Address.
				"
			::= { casaCmQueryEntry 1 }

		
		-- 1.3.6.1.4.1.20858.10.18.1.1.1.2
		casaQueryCmIpAddress OBJECT-TYPE
			SYNTAX IpAddress
			MAX-ACCESS read-only
			STATUS current
			DESCRIPTION
				"The cable modem Ip Address.
				"
			::= { casaCmQueryEntry 2 }

		
		-- 1.3.6.1.4.1.20858.10.18.1.1.1.3
		casaQueryCmTxTimeOffset OBJECT-TYPE
			SYNTAX Unsigned32
			MAX-ACCESS read-only
			STATUS current
			DESCRIPTION
				"A measure of the current round trip time at the CM, or the
				maximum round trip time seen by the CMTS.  Used for timing
				of CM upstream transmissions to ensure synchronized
				arrivals at the CMTS. Units are in terms of
				(6.25 microseconds/64).
				"
			::= { casaCmQueryEntry 3 }

		
		-- 1.3.6.1.4.1.20858.10.18.1.1.1.4
		casaQueryCmMicroReflection OBJECT-TYPE
			SYNTAX Integer32 (0..255)
			UNITS "dBc"
			MAX-ACCESS read-only
			STATUS current
			DESCRIPTION
				"Total microreflections including in-channel response
				as perceived on this interface, measured in dBc below
				the signal level.
				This object is not assumed to return an absolutely
				accurate value, but should give a rough indication
				of microreflections received on this interface.
				It is up to the implementor to provide information
				as accurate as possible.
				"
			::= { casaCmQueryEntry 4 }

		
		-- 1.3.6.1.4.1.20858.10.18.1.1.1.5
		casaQueryCmStatusTxPower OBJECT-TYPE
			SYNTAX TenthdBmV
			UNITS "dBmV"
			MAX-ACCESS read-only
			STATUS current
			DESCRIPTION
				"The operational transmit power of the cable modem downstream channel.
				"
			::= { casaCmQueryEntry 5 }

		
		-- 1.3.6.1.4.1.20858.10.18.1.1.1.6
		casaQueryCmStatusRxPower OBJECT-TYPE
			SYNTAX TenthdBmV
			UNITS "dBmV"
			MAX-ACCESS read-only
			STATUS current
			DESCRIPTION
				"The operational receive power of the cable modem upstream channel,the most current value (CM)
				or the value of 0
				    "
			::= { casaCmQueryEntry 6 }

		
		-- 1.3.6.1.4.1.20858.10.18.1.1.1.7
		casaQueryCmSigQSignalNoise OBJECT-TYPE
			SYNTAX TenthdB
			UNITS "dB"
			MAX-ACCESS read-only
			STATUS current
			DESCRIPTION
				"Signal/Noise ratio as perceived for this channel.
				describes the Signal/Noise of the upstream
				channel of CM . 
				"
			::= { casaCmQueryEntry 7 }

		
		-- 1.3.6.1.4.1.20858.10.18.1.1.1.8
		casaQueryCmtsSigQSignalNoise OBJECT-TYPE
			SYNTAX TenthdB
			UNITS "dB"
			MAX-ACCESS read-only
			STATUS obsolete
			DESCRIPTION
				"Signal/Noise ratio as perceived for this channel.
				describes the average Signal/Noiseof the upstream 
				channel of CMTS.
				
				"
			::= { casaCmQueryEntry 8 }
		
		-- 1.3.6.1.4.1.20858.10.18.1.1.1.9
		cmSysDesc OBJECT-TYPE
        	SYNTAX      DisplayString
        	MAX-ACCESS  read-only
        	STATUS      current
        	DESCRIPTION
            	"The model and software version of this CM  
	     		as parsed from its sysDescr.
	     		"
        	::= { casaCmQueryEntry 9 }
        
        -- 1.3.6.1.4.1.20858.10.18.1.1.1.10
        configFile OBJECT-TYPE
        	SYNTAX      DisplayString
        	MAX-ACCESS  read-only
        	STATUS      current
        	DESCRIPTION
            	"The configuration file of the modem.
            	"
        	::= { casaCmQueryEntry 10 }
		
		-- 1.3.6.1.4.1.20858.10.18.1.2
		casaQueryCmCommunityName OBJECT-TYPE
			SYNTAX OCTET STRING
			MAX-ACCESS read-write
			STATUS current
			DESCRIPTION
				"The read community string is used for polling the CMs.
				
				For SNMPv3, this object will contain a user name instead of a community string.
				
				For DOCSIS 3.0 cable modem ,if CommunityName is not set in configuration file of cable modem,  reading casaCmQueryTable will return 0 or TIMEOUT."
			::= { casaCmQueryMibObjects 2 }

		-- 1.3.6.1.4.1.20858.10.18.1.3
		casaCmPhyInfoTable OBJECT-TYPE
			SYNTAX SEQUENCE OF CasaCmPhyInfoEntry
			MAX-ACCESS not-accessible
			STATUS current
			DESCRIPTION
				"Table to record the physical infomation of cable modem."
			::= { casaCmQueryMibObjects 3 }

		
		-- 1.3.6.1.4.1.20858.10.18.1.3.1
		casaCmPhyInfoEntry OBJECT-TYPE
			SYNTAX CasaCmPhyInfoEntry
			MAX-ACCESS not-accessible
			STATUS current
			DESCRIPTION
				"Entry of table casaCmPhyInfoTable."
			INDEX { casaCmPhyInfoMacAddress, casaCmPhyInfoDir, casaCmPhyInfoIfIndex }
			::= { casaCmPhyInfoTable 1 }

		
		CasaCmPhyInfoEntry ::=
			SEQUENCE { 
				casaCmPhyInfoMacAddress
					MacAddress,
				casaCmPhyInfoDir
					IfDirection,
				casaCmPhyInfoIfIndex
					InterfaceIndex,
				casaCmPhyInfoSID
					Integer32,
				casaCmPhyInfoUSTxPower
					TenthdBmV,
				casaCmPhyInfoUsRxPower
					TenthdBmV,
				casaCmPhyInfoUSSignalNoise
					TenthdB,
				casaCmPhyInfoTxTimeOffset
					Unsigned32,
				casaCmPhyInfoMicroReflection
					Integer32,
				casaCmPhyInfoDSPower
					TenthdBmV,
				casaCmPhyInfoDSSignalNoise
					TenthdB,
				casaCmPhyInfoMode
					CasaDocsisUpstreamType
			 }

		-- 1.3.6.1.4.1.20858.10.18.1.3.1.1
		casaCmPhyInfoMacAddress OBJECT-TYPE
			SYNTAX MacAddress
			MAX-ACCESS not-accessible
			STATUS current
			DESCRIPTION
				"Mac address of cable modem."
			::= { casaCmPhyInfoEntry 1 }

		
		-- 1.3.6.1.4.1.20858.10.18.1.3.1.2
		casaCmPhyInfoDir OBJECT-TYPE
			SYNTAX IfDirection
			MAX-ACCESS not-accessible
			STATUS current
			DESCRIPTION
				"Upstream or downstream."
			::= { casaCmPhyInfoEntry 2 }

		
		-- 1.3.6.1.4.1.20858.10.18.1.3.1.3
		casaCmPhyInfoIfIndex OBJECT-TYPE
			SYNTAX InterfaceIndex
			MAX-ACCESS not-accessible
			STATUS current
			DESCRIPTION
				"IfIndex of upstream channel or downstream channel."
			::= { casaCmPhyInfoEntry 3 }

		
		-- 1.3.6.1.4.1.20858.10.18.1.3.1.4
		casaCmPhyInfoSID OBJECT-TYPE
			SYNTAX Integer32
			MAX-ACCESS read-only
			STATUS current
			DESCRIPTION
				"Primary sid."
			::= { casaCmPhyInfoEntry 4 }

		
		-- 1.3.6.1.4.1.20858.10.18.1.3.1.5
		casaCmPhyInfoUSTxPower OBJECT-TYPE
			SYNTAX TenthdBmV
			UNITS "dBmV"
			MAX-ACCESS read-only
			STATUS current
			DESCRIPTION
				"The operational transmit power for the attached upstream
 				channel of cable modem."
			::= { casaCmPhyInfoEntry 5 }

		
		-- 1.3.6.1.4.1.20858.10.18.1.3.1.6
		casaCmPhyInfoUsRxPower OBJECT-TYPE
			SYNTAX TenthdBmV
			UNITS "dBmV"
			MAX-ACCESS read-only
			STATUS current
			DESCRIPTION
				"The operational receive power for the attached upstream 
				channel of CMTS."
			::= { casaCmPhyInfoEntry 6 }

		
		-- 1.3.6.1.4.1.20858.10.18.1.3.1.7
		casaCmPhyInfoUSSignalNoise OBJECT-TYPE
			SYNTAX TenthdB
			UNITS "dB"
			MAX-ACCESS read-only
			STATUS current
			DESCRIPTION
				"Signal/Noise ratio as perceived for this channel.Describes 
				the Signal/Noise of the upstream channel of CMTS . "
			::= { casaCmPhyInfoEntry 7 }

		
		-- 1.3.6.1.4.1.20858.10.18.1.3.1.8
		casaCmPhyInfoTxTimeOffset OBJECT-TYPE
			SYNTAX Unsigned32
			MAX-ACCESS read-only
			STATUS current
			DESCRIPTION
				"A measure of the current round trip time at the CM, or the
				maximum round trip time seen by the CMTS.  Used for timing
				of CM upstream transmissions to ensure synchronized
				arrivals at the CMTS. Units are in terms of
				(6.25 microseconds/64).
				"
			::= { casaCmPhyInfoEntry 8 }

		
		-- 1.3.6.1.4.1.20858.10.18.1.3.1.9
		casaCmPhyInfoMicroReflection OBJECT-TYPE
			SYNTAX Integer32
			UNITS "dBc"
			MAX-ACCESS read-only
			STATUS current
			DESCRIPTION
				"Total microreflections including in-channel response
				as perceived on this interface, measured in dBc below
				the signal level.
				This object is not assumed to return an absolutely
				accurate value, but should give a rough indication
				of microreflections received on this interface.
				It is up to the implementor to provide information
				as accurate as possible.
				"
			::= { casaCmPhyInfoEntry 9 }

		
		-- 1.3.6.1.4.1.20858.10.18.1.3.1.10
		casaCmPhyInfoDSPower OBJECT-TYPE
			SYNTAX TenthdBmV
			UNITS "dBmV"
			MAX-ACCESS read-only
			STATUS current
			DESCRIPTION
				"The operational transmit power of the cable modem downstream 
				channel"
			::= { casaCmPhyInfoEntry 10 }

		
		-- 1.3.6.1.4.1.20858.10.18.1.3.1.11
		casaCmPhyInfoDSSignalNoise OBJECT-TYPE
			SYNTAX TenthdB
			UNITS "dB"
			MAX-ACCESS read-only
			STATUS current
			DESCRIPTION
				"Signal/Noise ratio as perceived for this channel.Describes 
				the Signal/Noise of the downstream channel of CM . "
			::= { casaCmPhyInfoEntry 11 }

		
		-- 1.3.6.1.4.1.20858.10.18.1.3.1.12
		casaCmPhyInfoMode OBJECT-TYPE
			SYNTAX CasaDocsisUpstreamType
			MAX-ACCESS read-only
			STATUS current
			DESCRIPTION
				"This attribute indicates modulation type statuscurrently 
				used by the CM for this upstream channel. Sincethis object 
				specifically identifies PHY Layermode, the shared upstream 
				channel type 'tdmaAndAtdma'is not permitted."
			::= { casaCmPhyInfoEntry 12 }
		

		-- 1.3.6.1.4.1.20858.10.18.2
		casaCmQueryGroups OBJECT IDENTIFIER ::= { casaCmQueryMib 2 }

		
		-- 1.3.6.1.4.1.20858.10.18.2.1
		casaCmQueryroup OBJECT-GROUP
			OBJECTS { casaQueryCmIpAddress, casaQueryCmTxTimeOffset, casaQueryCmMicroReflection, casaQueryCmStatusTxPower, casaQueryCmStatusRxPower, 
				casaQueryCmSigQSignalNoise, casaQueryCmtsSigQSignalNoise, cmSysDesc, configFile,casaQueryCmCommunityName, casaCmPhyInfoMacAddress, casaCmPhyInfoDir, casaCmPhyInfoIfIndex, 
				casaCmPhyInfoSID, casaCmPhyInfoUSTxPower, casaCmPhyInfoUsRxPower, casaCmPhyInfoUSSignalNoise, casaCmPhyInfoTxTimeOffset, 
				casaCmPhyInfoMicroReflection, casaCmPhyInfoDSPower, casaCmPhyInfoDSSignalNoise, casaCmPhyInfoMode }
			STATUS current
			DESCRIPTION 
				"
				"
			::= { casaCmQueryGroups 1 }

		
		-- 1.3.6.1.4.1.20858.10.18.3
		casaCmQueryCompliances OBJECT IDENTIFIER ::= { casaCmQueryMib 3 }

		
		-- 1.3.6.1.4.1.20858.10.18.3.1
		casaCmQueryCompliance MODULE-COMPLIANCE
			STATUS current
			DESCRIPTION 
				"Description."
			MODULE -- this module
				MANDATORY-GROUPS { casaCmQueryroup }
			::= { casaCmQueryCompliances 1 }

		
	
	END

--
-- CASA-CABLE-CMQUERY-MIB.my
--
